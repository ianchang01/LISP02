;;modify by Ianchang001
(defun c:pt_out1()
 (setq ss (ssget '((0 . "LINE"))))
 (setq csv_file (getfiled "Export file" "D:\\" "csv" 1))
 (setq fw (open csv_file "w"))
 (setq n 0)
 (repeat (sslength ss)
   (setq ent  (ssname ss n))
   (setq data (entget ent))
   (setq p1 (cdr (assoc 10 data))
	 p2 (cdr (assoc 11 data)))
   (setq x1 (car p1) y1 (cadr p1)
	 x2 (car p2) y2 (cadr p2))
   (setq str (strcat (rtos x1) "," (rtos y1) "," (rtos x2) "," (rtos y2)))
   (write-line str fw)
   (setq n (1+ n))
 )
 (close fw)
 (princ)
)

(defun c:pt_out2()
 (prompt "\nSelect lines...")
 (setq ss (ssget '((0 . "LINE"))))
 (if ss
    (progn
      (get_pt_list)  
      (export_file)  
    )
    (alert "Not found!")
 )  
 (princ) 
)

(defun get_pt_list()
 (setq pt_list nil)
 (setq n 0)
 (repeat (sslength ss)
   (setq ent  (ssname ss n))
   (setq data (entget ent))
   (setq p1 (cdr (assoc 10 data))
	 p2 (cdr (assoc 11 data)))
   (setq pt_list (cons (list p1 p2) pt_list))
   (setq n (1+ n))
 )
)

(defun export_file()
 (setq csv_file (getfiled "Export file" "D:\\" "csv" 1))
 (setq fw (open csv_file "w"))
 (foreach item pt_list
   (setq p1 (nth 0 item))
   (setq p2 (nth 1 item))
   (setq x1 (car p1) y1 (cadr p1)
	 x2 (car p2) y2 (cadr p2))
   (setq str (strcat (rtos x1) "," (rtos y1) "," (rtos x2) "," (rtos y2)))
   (write-line str fw)
 )
 (close fw)
 (alert "points data exported.")
 (princ)
)

(defun c:pt_in1()
  (setvar "cmdecho" 0)
  (setq csv_file (getfiled "Import file" "D:\\" "csv" 4))
  (setq fr (open csv_file "r"))
  (while (setq str (read-line fr))
;;;    (setq str "1545.9903,642.8007,1545.9903,648.0731")
    (setq $n (vl-string-search "," str))
    (setq x1 (substr str 1 $n))
    (setq str (substr str (+ $n 2)))
    (setq $n (vl-string-search "," str))
    (setq y1 (substr str 1 $n))
    (setq str (substr str (+ $n 2)))
    (setq $n (vl-string-search "," str))
    (setq x2 (substr str 1 $n))
    (setq y2 (substr str (+ $n 2)))
    (command ".line" (list (atof x1) (atof y1)) (list (atof x2) (atof y2)) "")
  )
  (close fr)
  (command ".zoom" "e")
  (princ)
)


(defun c:pt_in2()
  (setvar "cmdecho" 0)
  (setq csv_file (getfiled "Import file" "D:\\" "csv" 4))
  (load "ReadCSV")
  (setq data (LM:readcsv csv_file))
  (foreach item data
     (setq x1 (nth 0 item)
	   y1 (nth 1 item)
	   x2 (nth 2 item)
	   y2 (nth 3 item))
     (setq p1 (list (atof x1) (atof y1))
           p2 (list (atof x2) (atof y2)))
     (command ".line" p1 p2 "")
  ) 	   
  (command ".zoom" "e")
  (princ)
)
