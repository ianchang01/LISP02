;;Ex clone by Ian
;;modify by Ianchang001
;;     p3    
;;           
;; p1  p0  p2
;;           
;;     p4    
(defun c:my_cricle(/ p0 p1 p2 p3 p4)
  (setvar "cmdecho" 0)
  (setq oldla (getvar "clayer"))
  (setq oldos (getvar "osmode"))
;;;  (setq p0  (getpoint "\nCenter point: "))
  (setq rad (getdist "\nRadius: "))
  (setq ext (getdist "\nExtension: "))
  (setvar "osmode" 0)
  (while (setq p0 (getpoint "\nCenter point: (press <Enter> to exit)"))
    (setq p1 (polar p0 pi (+ rad ext)))   
    (setq p2 (polar p0  0 (+ rad ext)))
    (setq p3 (polar p0 (* 0.5 pi) (+ rad ext)))
    (setq p4 (polar p0 (* 1.5 pi) (+ rad ext)))
    (setvar "clayer" "0")
    (command ".circle" p0 rad)
    (set_layer "center" 4 "center")
    (command ".line" p1 p2 "")
    (command ".line" p3 p4 "")
  )
  (setvar "clayer" oldla)
  (setvar "osmode" oldos)
  (princ)
)

;;         p7        
;;    P4---------p3  
;;    |          |   
;; p5 |    p0    | p6
;;    |          |   
;;    P1--------p2   
;;         p8        
(defun c:my_rectangle()
  (setvar "cmdecho" 0)
  (setq p0 (getpoint "\nCenter point: "))
  (setq w  (getdist "\nWidth: "))
  (setq h  (getdist "\nHeight: "))
  (setq ext (getdist "\nExtension: "))
  (setq dx (/ w 2)
	dy (/ h 2)
  )
  (setq p1 (list (- (car p0) dx) (- (cadr p0) dy))
  	p2 (list (+ (car p0) dx) (- (cadr p0) dy))
  	p3 (list (+ (car p0) dx) (+ (cadr p0) dy))
  	p4 (list (- (car p0) dx) (+ (cadr p0) dy))
  	p5 (polar p0 pi (+ dx ext))
  	p6 (polar p0  0 (+ dx ext))
  	p7 (polar p0 (* 0.5 pi) (+ dy ext))
  	p8 (polar p0 (* 1.5 pi) (+ dy ext))
  )
  (setvar "clayer" "0")
  (command ".line" p1 p2 p3 p4 "c")
  (setvar "clayer" "center")
  (command ".line" p5 p6 "")
  (command ".line" p7 p8 "")
  (setvar "clayer" "0")
  (princ)
)

(defun c:my_fun()
  (initget "1 2")
  (setq ans (getkword "\n1.Cricle/2.Rectangle<2>: "))
  (if (not ans) (setq ans "2"))
;;;  (if (= ans nil) (setq ans "2"))
  (if (= ans "1")
      (my_cricle)
      (my_rectangle)
  )
  (princ)
)

(defun my_cricle(/ p0 p1 p2 p3 p4)
  (setvar "cmdecho" 0)
  (setq oldla (getvar "clayer"))
  (setq oldos (getvar "osmode"))
  (setq p0  (getpoint "\n中心點: "))
  (setq rad (getdist p0 "\n半徑: "))
  (setq ext (getdist "\n延伸量: "))
  ;;距離=半徑+延伸量
  (setq p1 (polar p0 pi (+ rad ext)))   
  (setq p2 (polar p0  0 (+ rad ext)))
  (setq p3 (polar p0 (* 0.5 pi) (+ rad ext)))
  (setq p4 (polar p0 (* 1.5 pi) (+ rad ext)))
  (setvar "clayer" "0")
  (setvar "osmode" 0)
  (command ".circle" p0 rad)
  (set_layer "center" 4 "center")
  (command ".line" p1 p2 "")
  (command ".line" p3 p4 "")
  (setvar "clayer" oldla)
  (setvar "osmode" oldos)
  (princ)
)

(defun my_rectangle()
  (setvar "cmdecho" 0)
  (setq oldla (getvar "clayer"))
  (setq oldos (getvar "osmode"))
  (setq p0 (getpoint "\n中心點: "))
  (setq w  (getdist "\n寬度: "))
  (setq h  (getdist "\n高度: "))
  (setq ext (getdist "\n延伸量: "))
  (setq dx (/ w 2)
	dy (/ h 2)
  )
  (setq p1 (list (- (car p0) dx) (- (cadr p0) dy))
  	p2 (list (+ (car p0) dx) (- (cadr p0) dy))
  	p3 (list (+ (car p0) dx) (+ (cadr p0) dy))
  	p4 (list (- (car p0) dx) (+ (cadr p0) dy))
  	p5 (polar p0 pi (+ dx ext))
  	p6 (polar p0  0 (+ dx ext))
  	p7 (polar p0 (* 0.5 pi) (+ dy ext))
  	p8 (polar p0 (* 1.5 pi) (+ dy ext))
  )
  (setvar "clayer" "0")
  (setvar "osmode" 0)
  (command ".line" p1 p2 p3 p4 "c")
  (set_layer "center" 4 "center")
  (command ".line" p5 p6 "")
  (command ".line" p7 p8 "")
  (setvar "clayer" oldla)
  (setvar "osmode" oldos)
  (princ)
)

(defun c:con_circle()
  (setvar "cmdecho" 0)
  (setq p0 (getpoint "\n中心點: "))
  (setq rad (getdist p0 "\n半徑: "))
  (setq add (getdist "\n增量: "))
  (initget 7)
  (setq n (getint "\n數量: "))
  (repeat n
    (command ".circle" p0 rad)
    (setq rad (+ rad add))
  )
  (princ)
)


(defun set_layer(lname col ltype)
  (if (tblsearch "LAYER" lname)
      (setvar "clayer" lname)
      (command ".layer" "m" lname "c" col lname "L" ltype lname "")
  )
)

(defun c:draw_center(/ p0 p1 p2 p3 p4)
  (setvar "cmdecho" 0)
  (setq oldla (getvar "clayer"))
  (setq oldos (getvar "osmode"))
  (setq ext 3)
  (setvar "osmode" 0)
  (set_layer "center" 4 "center")
  (while (setq tmp (entsel "\n選取圓: "))
    (setq ent (car tmp))
    (setq data (entget ent))
    (setq p0 (cdr (assoc 10 data)))
    (setq rad (cdr (assoc 40 data)))
;;;    (setvar "osmode" 0)
    (setq p1 (polar p0 pi (+ rad ext)))
    (setq p2 (polar p0 0 (+ rad ext)))
    (setq p3 (polar p0 (* 0.5 pi) (+ rad ext)))
    (setq p4 (polar p0 (* 1.5 pi) (+ rad ext)))
;;;    (set_layer "center" 4 "center")
    (command ".line" p1 p2 "")
    (command ".line" p3 p4 "")
  )
  (setvar "clayer" oldla)
  (setvar "osmode" oldos)
  (princ)
)

(defun c:chg_rad()
  (setvar "cmdecho" 0)
  (while (setq tmp (entsel "\n選取圓: "))
    (setq rad (getdist "\n新的半徑: "))
    (setq ent (car tmp))
    (setq data (entget ent))
    (setq old (assoc 40 data))    ;;(40 . 目前值)
    (setq new (cons 40 rad))      ;;(40 . 新半徑)
    (setq data2 (subst new old data))
    (entmod data2)
  )  
  (princ)
)

(defun c:chg_pt()
  (setvar "cmdecho" 0)
  (while (setq tmp (entsel "\n選取圓: "))
    (setq pt  (getpoint "\n新的中心點: "))
    (setq ent (car tmp))
    (setq data (entget ent))
    (setq old (assoc 10 data))    
    (setq new (cons 10 pt))      
    (setq data2 (subst new old data))
    (entmod data2)
  )  
  (princ)
)

(defun c:chg_txt()
  (setvar "cmdecho" 0)
  (while (setq tmp (entsel "\n選取文字: "))
    (setq str (getstring t "\n新的內容: "))
    (setq ent (car tmp))
    (setq data (entget ent))
    (setq old (assoc 1 data))    
    (setq new (cons 1 str))      
    (setq data2 (subst new old data))
    (entmod data2)
  )  
  (princ)
)

(defun c:rfile()
  (setq fr (open "D:\\temp\\sample.txt" "r"))
  (setq pt (getpoint "\n插入點: "))
  (setq h  (getdist pt "\n字高: "))
  
 (while (setq str (read-line fr))
   (command ".text" pt h 0 str) 
   (setq pt (polar pt (* 1.5 pi) (* 1.5 h)))
 )
  (close fr)
)  

(defun c:wfile()
  (setq ent (car (entsel "\n選取物件: ")))
  (setq txt (cdr (assoc 1 (entget ent))))
  (setq fw (open "d:\\temp\\aa.txt" "a"))
  (write-line txt fw)
  (close fw)
)
